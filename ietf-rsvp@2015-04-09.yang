module ietf-rsvp {

    namespace "urn:ietf:params:xml:ns:yang:ietf-rsvp";

    /* Replace with IANA when assigned */
    prefix "rsvp";

    /* import ietf-inet-types { prefix inet; } */
    import ietf-interfaces {
        prefix "if";
    }

    import ietf-inet-types {
        prefix inet;
    }

    import ietf-routing {
      prefix "rt";
    }
    
    organization
        "IETF TEAS Working Group";

    contact "TBA";

    description
        "This module contains the RSVP YANG data model.";

    revision 2015-04-09 {
        description "Initial revision.";
        reference "RFC2205";
    }

    identity rsvp {
      base "rt:routing-protocol";
      description "RSVP";
    }

    /* RSVP features */
    feature authentication {
        description
            "Indicates support for RSVP authentication";
    }

    feature graceful-restart {
        description
            "Indicates support for RSVP graceful restart";
    }

    feature refresh-reduction {
        description
            "Indicates support for RSVP refresh reduction";
    }

    feature hellos {
        description
            "Indicates support for RSVP hellos";
    }

    grouping graceful-restart {
        description "Configure RSVP Graceful-Restart parameters.";
        container graceful-restart {
            if-feature graceful-restart;
            presence "Enable RSVP graceful restart on the node.";
            description
                "RSVP graceful-restart parameters container";

            leaf restart-time {
                type uint32;
                description
                    "Graceful restart time (seconds).";
                reference
                    "RFC 5495: Description of the Resource
                    Reservation Protocol - Traffic-Engineered
                    (RSVP-TE) Graceful Restart Procedures";
            }
            leaf recovery-time {
                type uint32;
                description
                    "RSVP state recovery time";
            }
        }
    }

    grouping authentication {
        description
            "RSVP authentication grouping";
        container authentication {
            if-feature authentication;
            description
                "Configure RSVP authentication.";
            leaf key-chain {
                type string {
                     length "1..32";
                }
                description
                    "Key chain name to authenticate RSVP signaling
                    messages.";
                reference
                    "RFC 2747: RSVP Cryptographic Authentication";
            }
            leaf lifetime {
                type uint32 {
                     range "30..86400";
                }
                description 
                    "Life time for each security association";
                reference
                    "RFC 2747: RSVP Cryptographic Authentication";
            }
            leaf window-size {
                type uint32 {
                    range "1..64";
                }
                description
                    "Window-size to limit number of out-of-order
                    messages.";
                reference
                    "RFC 2747: RSVP Cryptographic Authentication";
            }
            leaf challenge {
                type empty;
                description
                    "Enable challenge messages.";
                reference
                    "RFC 2747: RSVP Cryptographic Authentication";
            }
            leaf retransmits {
                type uint32 {
                    range "1..10000";
                }
                description
                    "Number of retransmits when messages are
                     dropped.";
                reference
                    "RFC 2747: RSVP Cryptographic Authentication";
            }
        }
    }

    grouping signaling {
        description
            "RSVP signaling properties grouping";
        container signaling {
            description
                "RSVP signaling properties container";
            uses graceful-restart;
            container hello {
                if-feature hellos;
                description "Configure Hello parameters.";
                leaf interface-based {
                     type empty;
                     description "Enable interface-based
                                  Hello adjacency if present.";
                }
                leaf hello-interval {
                    type uint32 {
                        range "3000..30000";
                    }
                    description
                        "Configure interval between successive Hello
                        messages in milliseconds.";
                    reference
                        "RFC 3209: RSVP-TE: Extensions to RSVP for
                        LSP Tunnels.
                        RFC 5495: Description of the Resource
                        Reservation Protocol - Traffic-Engineered
                        (RSVP-TE) Graceful Restart Procedures";
                }
                leaf hello-misses {
                    type uint32 {
                         range "1..10";
                    }
                    description
                        "Configure max number of consecutive missed
                        Hello messages.";
                    reference
                        "RFC 3209: RSVP-TE: Extensions to RSVP for
                        LSP Tunnels RFC 5495: Description of the
                        Resource Reservation Protocol - Traffic-
                        Engineered (RSVP-TE) Graceful Restart
                        Procedures";
                }
            }

            container path-err {
                description
                    "RSVP path-state removal behavior";
                leaf state-removal {
                    type empty;
                    description
                        "State-Removal flag in Path Error message
                        if present.";
                }
            }

            container refresh {
                description
                    "RSVP refreshes properties";
                leaf interval {
                    type uint32;
                    description
                        "Set interval between successive refreshes";
                }
                leaf missed {
                    type uint32;
                    description
                        "Set max number of consecutive missed
                         messages for state expiry";
                }

                container reduction {
                    if-feature refresh-reduction;
                    description
                        "Configure RSVP Refresh Reduction
                         parameters.";
                    leaf bundle-message-max-size {
                        type uint32 {
                            range "512..65000";
                        }
                        description
                            "Configure maximum size (bytes) of a
                             single RSVP Bundle message.";
                    }
                    leaf disable {
                        type empty;
                        description
                            "Disable refresh reduction if present.";
                    }
                    leaf reliable-ack-hold-time {
                        type uint32 {
                            range "100..5000";
                        }
                        description
                            "Configure hold time in milliseconds for
                            sending RSVP ACK message(s).";
                    }
                    leaf reliable-ack-max-size {
                        type uint32 {
                            range "20..65000";
                        }
                        description
                            "Configure max size of a single RSVP ACK
                            message.";
                    }
                    leaf reliable-retransmit-time {
                        type uint32 {
                            range "100..10000";
                        }
                        description
                            "Configure min delay in milliseconds to
                             wait for an ACK before a retransmit.";
                    }
                    leaf reliable-srefresh {
                        type empty;
                        description
                            "Configure use of reliable messaging for
                            summary refresh if present.";
                    }
                    leaf summary-max-size {
                        type uint32 {
                            range "20..65000";
                        }
                        description
                            "Configure max size (bytes) of a single
                             RSVP summary refresh message.";
                    }
                }
            }
        }
    }

  grouping rsvp-container {
    description "RSVP top container.";
    container rsvp {
        presence "Enable RSVP feature";
        description "RSVP feature container";
        container globals {
            description "RSVP global properties.";
            uses signaling;
        }

        container interfaces {
            description
                "RSVP interfaces container";
            uses authentication;
            uses signaling;
            list interface {
                key "interface";
                description
                    "RSVP interfaces.";
                leaf interface {
                     type if:interface-ref;
                     description
                        "RSVP interface.";
                }
                uses authentication;
                uses signaling;
            }
        }

        container sessions {
            description
                "RSVP sessions container";
            list session {
                key "src_port dst_port source destination";
                description
                    "List of RSVP sessions";
                leaf src_port {
                    type uint16;
                    description "RSVP source port";
                    reference "RFC2205";
                }
                leaf dst_port {
                    type uint16;
                    description "RSVP destination port";
                    reference "RFC2205";
                }
                leaf source {
                    type inet:ip-address;
                    description "RSVP source address";
                    reference "RFC2205";
                }
                leaf destination {
                    type inet:ip-address;
                    description "RSVP destination address";
                    reference "RFC2205";
                }
            }
        }

        container neighbors {
            description
                "RSVP neighbors container";
            list neighbor {
                key "address";
                description
                    "List of RSVP neighbors";
                leaf address {
                    type inet:ip-address;
                    description
                        "Neighbor address";
                }
            }
        }

/**** Moving to state branch 
        container interface-state {
            config "false";
            description
                "RSVP interfaces state";
            list session {
                key "interface";
                description
                    "RSVP interfaces state.";
                leaf interface {
                     type if:interface-ref;
                     description
                        "RSVP interface.";
                }
            }
        }

        container sessions-state {
            config "false";
            description
                "RSVP sessions state";
            list session {
                key "src_port dst_port source destination";
                description
                    "List of RSVP sessions";
                leaf src_port {
                    type uint16;
                    description "RSVP source port";
                    reference "RFC2205";
                }
                leaf dst_port {
                    type uint16;
                    description "RSVP destination port";
                    reference "RFC2205";
                }
                leaf source {
                    type inet:ip-address;
                    description "RSVP source address";
                    reference "RFC2205";
                }
                leaf destination {
                    type inet:ip-address;
                    description "RSVP destination address";
                    reference "RFC2205";
                }
            }
        }

        container neighbors-state {
            config "false";
            description
                "RSVP neighbors state";
            list neighbor {
                key "address";
                description
                    "List of RSVP neighbors";
                leaf address {
                    type inet:ip-address;
                    description
                        "Neighbor address";
                }
            }
        }
****/
    }
  } // grouping rsvp-container

  /*
   * Configuration data nodes
   */
  augment "/rt:routing/rt:routing-instance/"
    + "rt:routing-protocols/rt:routing-protocol" {
    when "rt:type = 'rsvp:rsvp'" {
      description
        "This augment is only valid for a protocol instance
        of RSVP.";
    }
    description "RSVP augmentation.";
    uses rsvp-container;
  }

  /*
   * Operational state data nodes
   */
  augment "/rt:routing-state/rt:routing-instance/"
    + "rt:routing-protocols/rt:routing-protocol" {
    when "rt:type = 'rsvp:rsvp'" {
      description
        "This augment is only valid for a protocol instance
        of RSVP.";
    }
    description "RSVP augmentation.";
    uses rsvp-container;
  }

  /*
   * RPCs
   */

  /*
   * Notifications
   */
}
