module ietf-rsvp-te {
  yang-version 1.1;
  namespace "urn:ietf:params:xml:ns:yang:ietf-rsvp-te";
  prefix rsvp-te;

  import ietf-rsvp {
    prefix rsvp;
    reference
      "draft-ietf-teas-yang-rsvp: A YANG Data Model for
       Resource Reservation Protocol (RSVP)";
  }
  import ietf-routing {
    prefix rt;
    reference
      "RFC8349: A YANG Data Model for Routing Management";
  }
  import ietf-routing-types {
    prefix rt-types;
    reference
      "RFC8294: Common YANG Data Types for the Routing Area";
  }
  import ietf-te {
    prefix te;
    reference
      "draft-ietf-teas-yang-te: A YANG Data Model for Traffic
       Engineering Tunnels and Interfaces";
  }
  import ietf-te-device {
    prefix te-dev;
    reference
      "draft-ietf-teas-yang-te: A YANG Data Model for Traffic
       Engineering Tunnels and Interfaces";
  }

  /* Import TE generic types */

  import ietf-te-types {
    prefix te-types;
    reference
      "RFC8776: Common YANG Data Types for Traffic Engineering.";
  }
  import ietf-inet-types {
    prefix inet;
    reference
      "RFC6991: Common YANG Data Types";
  }

  organization
    "IETF Traffic Engineering Architecture and Signaling (TEAS)
     Working Group";
  contact
    "WG Web:   <http://tools.ietf.org/wg/teas/>
     WG List:  <mailto:teas@ietf.org>

     Editor:   Vishnu Pavan Beeram
               <mailto:vbeeram@juniper.net>

     Editor:   Tarek Saad
               <mailto:tsaad.net@gmail.com>

     Editor:   Rakesh Gandhi
               <mailto:rgandhi@cisco.com>

     Editor:   Xufeng Liu
               <mailto: xufeng.liu.ietf@gmail.com>

     Editor:   Igor Bryskin
               <mailto:Igor.Bryskin@huawei.com>

     Editor:   Himanshu Shah
               <mailto:hshah@ciena.com>";
  description
    "This module contains the RSVP-TE YANG generic data model.
     The model fully conforms to the Network Management Datastore
     Architecture (NMDA).

     Copyright (c) 2018 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).
     This version of this YANG module is part of RFC XXXX; see
     the RFC itself for full legal notices.";

  // RFC Ed.: replace XXXX with actual RFC number and remove this
  // note.
  // RFC Ed.: update the date below with the date of RFC publication
  // and remove this note.

  revision 2020-03-09 {
    description
      "A YANG Data Model for RSVP-TE";
    reference
      "RFCXXXX: A YANG Data Model for RSVP-TE Protocol";
  }

  identity rsvp-message-type {
    description
      "RSVP message types";
  }

  identity rsvp-message-path {
    base rsvp-message-type;
    description
      "RSVP Path message";
    reference
      "RFC2205";
  }

  identity rsvp-message-resv {
    base rsvp-message-type;
    description
      "RSVP Resv message";
    reference
      "RFC2205";
  }

  identity rsvp-message-path-err {
    base rsvp-message-type;
    description
      "RSVP Path-Err message";
    reference
      "RFC2205";
  }

  identity rsvp-message-resv-err {
    base rsvp-message-type;
    description
      "RSVP Resv-Err message";
    reference
      "RFC2205";
  }

  identity rsvp-message-path-tear {
    base rsvp-message-type;
    description
      "RSVP Path Tear message";
    reference
      "RFC2205";
  }

  identity rsvp-message-resv-conf {
    base rsvp-message-type;
    description
      "RSVP Resv Confirm message";
    reference
      "RFC2205";
  }

  identity rsvp-message-srefresh {
    base rsvp-message-type;
    description
      "RSVP SRefresh message";
    reference
      "RFC2961";
  }

  identity rsvp-message-hello {
    base rsvp-message-type;
    description
      "RSVP Hello message";
    reference
      "RFC3209";
  }

  identity rsvp-message-bundle {
    base rsvp-message-type;
    description
      "RSVP Bundle message";
    reference
      "RFC2961";
  }

  identity rsvp-message-notify {
    base rsvp-message-type;
    description
      "RSVP Notify message";
    reference
      "RFC3473";
  }

  /**
   * RSVP-TE LSPs groupings.
   */

  grouping lsp-record-route-information-state {
    description
      "recorded route information grouping";
    container incoming-record-route-subobjects {
      description
        "RSVP recorded route object incoming information";
      list incoming-record-route-subobject {
        when "../../te:origin-type != 'ingress'" {
          description
            "Applicable on non-ingress LSPs only";
        }
        key "index";
        ordered-by user;
        description
          "List of RSVP Path record-route objects";
        uses te-types:record-route-state;
      }
    }
    container outgoing-record-route-subobjects {
      description
        "RSVP recorded route object outgoing information";
      list outgoing-record-route-subobject {
        when "../../te:origin-type != 'egress'" {
          description
            "Applicable on non-egress LSPs only";
        }
        key "index";
        ordered-by user;
        description
          "List of RSVP Resv record-route objects";
        uses te-types:record-route-state;
      }
    }
  }

  grouping lsp-explicit-route-information-state {
    description
      "RSVP-TE LSP explicit-route information";
    container explicit-route-objects {
      description
        "Explicit route object information";
      list incoming-explicit-route-hop {
        when "../../te:origin-type != 'ingress'" {
          description
            "Applicable on non-ingress LSPs only";
        }
        key "index";
        ordered-by user;
        description
          "List of incoming RSVP Path explicit-route objects";
        leaf index {
          type uint32;
          description
            "Explicit route hop index. The index is used to
             identify an entry in the list. The order of entries
             is defined by the user without relying on key values";
        }
        uses te-types:explicit-route-hop;
      }
      list outgoing-explicit-route-hop {
        when "../../te:origin-type != 'egress'" {
          description
            "Applicable on non-egress LSPs only";
        }
        key "index";
        ordered-by user;
        description
          "List of outgoing RSVP Path explicit-route objects";
        leaf index {
          type uint32;
          description
            "Explicit route hop index. The index is used to
             identify an entry in the list. The order of entries
             is defined by the user without relying on key values";
        }
        uses te-types:explicit-route-hop;
      }
    }
  }

  grouping lsp-attributes-flags {
    description
      "Configuration parameters relating to RSVP-TE LSP
       attribute flags";
    leaf-list lsp-attribute {
      type identityref {
        base te-types:lsp-attributes-flags;
      }
      description
        "RSVP per LSP attributes flags";
      reference
        "RFC4920, RFC5420, RFC7570";
    }
  }

  grouping lsp-session-attributes-obj-flags {
    description
      "Configuration parameters relating to RSVP-TE LSP
       session attribute flags";
    reference
      "RFC4859: Registry for RSVP-TE Session Flags";
    leaf-list session-attribute {
      when "../session-attribute !=
            'te-types:bandwidth-protection-desired' or
            ../session-attribute !=
            'te-types:soft-preemption-desired'" {
        description
          "Session attributes applicable to generic technologies
           only.";
      }
      type identityref {
        base te-types:session-attributes-flags;
      }
      description
        "RSVP session attributes flags";
      reference
        "RFC4859: Registry for RSVP-TE Session Flags";
    }
  }

  grouping lsp-properties {
    description
      "Configuration parameters relating to RSVP-TE LSP
       session attribute flags";
    leaf lsp-signaled-name {
      type string;
      description
        "Sets the session name to use in the session
         attribute object.";
    }
    uses lsp-session-attributes-obj-flags;
    uses lsp-attributes-flags;
  }

  grouping tunnel-properties {
    description
      "RSVP-TE Tunnel properties grouping";
    leaf retry-timer {
      type uint16 {
        range "1..600";
      }
      units "seconds";
      description
        "sets the time between attempts to establish the
         LSP";
    }
  }

  /*** End of RSVP-TE LSP groupings ***/
  /**
   * RSVP-TE generic global properties.
   */

  grouping global-soft-preemption {
    description
      "Configuration for global RSVP-TE soft preemption";
    leaf soft-preemption-timeout {
      type uint16 {
        range "0..300";
      }
      default "0";
      units "seconds";
      description
        "Timeout value for soft preemption to revert
         to hard preemption";
    }
  }

  grouping global-soft-preemption {
    description
      "Top level group for RSVP-TE soft-preemption";
    container global-soft-preemption {
      presence "Enables soft preemption on a node.";
      description
        "Top level container for RSVP-TE soft-preemption";
      uses global-soft-preemption;
    }
  }

  /*** End of RSVP-TE generic global properties. ***/
  /**
   * RSVP-TE interface generic groupings.
   */

  grouping rsvp-te-interface-attributes {
    description
      "Top level grouping for RSVP-TE interface properties.";
    container rsvp-te-interface-attributes {
      description
        "Top level container for RSVP-TE interface
         properties";
    }
  }

  /*** End of RSVP-TE generic groupings ***/
  /* RSVP-TE global properties */

  augment "/rt:routing/rt:control-plane-protocols/"
        + "rt:control-plane-protocol/rsvp:rsvp/rsvp:globals" {
    description
      "RSVP-TE augmentation to RSVP globals";
    uses global-soft-preemption;
  }

  /* Linkage to the base RSVP all links */

  augment "/rt:routing/rt:control-plane-protocols/"
        + "rt:control-plane-protocol/rsvp:rsvp/rsvp:interfaces" {
    description
      "RSVP-TE generic data augmentation pertaining to interfaces";
    uses rsvp-te-interface-attributes;
  }

  /* Linkage to per RSVP interface */

  augment "/rt:routing/rt:control-plane-protocols/"
        + "rt:control-plane-protocol/rsvp:rsvp/rsvp:interfaces/"
        + "rsvp:interface" {
    description
      "RSVP-TE generic data augmentation pertaining to specific
       interface";
    uses rsvp-te-interface-attributes;
  }

  /* add augmentation for sessions and neighbors */

  augment "/rt:routing/rt:control-plane-protocols/"
        + "rt:control-plane-protocol/rsvp:rsvp/rsvp:globals/"
        + "rsvp:sessions" {
    description
      "RSVP-TE generic data augmentation pertaining to session";
    list session-te {
      key "tunnel-endpoint tunnel-id extended-tunnel-id";
      config false;
      description
        "List of RSVP sessions";
      leaf tunnel-endpoint {
        type inet:ip-address;
        description
          "XX";
      }
      leaf tunnel-id {
        type uint16;
        description
          "XX";
      }
      leaf extended-tunnel-id {
        type inet:ip-address;
        description
          "XX";
      }
      uses rsvp:session-attributes-state;
    }
  }

  augment "/rt:routing/rt:control-plane-protocols/"
        + "rt:control-plane-protocol/rsvp:rsvp/rsvp:globals/"
        + "rsvp:sessions/session-te/psbs/psb" {
    description
      "RSVP-TE generic data augmentation pertaining to session";
    /* To be added */
    leaf tspec-average-rate {
      type rt-types:bandwidth-ieee-float32;
      units "Bytes per second";
      description
        "Tspec Token Bucket Average Rate";
      reference
        "RFC2210: RSVP with INTSERV";
    }
    leaf tspec-size {
      type rt-types:bandwidth-ieee-float32;
      units "Bytes per second";
      description
        "Tspec Token Bucket Burst Rate";
      reference
        "RFC2210";
    }
    leaf tspec-peak-rate {
      type rt-types:bandwidth-ieee-float32;
      units "Bytes per second";
      description
        "Tspec Token Bucket Peak Data Rate";
      reference
        "RFC2210";
    }
    leaf min-policed-unit {
      type uint32;
      description
        "Tspec Minimum Policed Unit";
      reference
        "RFC2210";
    }
    leaf max-packet-size {
      type uint32;
      description
        "Tspec Maximum Packet Size";
      reference
        "RFC2210";
    }
  }

  augment "/rt:routing/rt:control-plane-protocols/"
        + "rt:control-plane-protocol/rsvp:rsvp/rsvp:globals/"
        + "rsvp:sessions/session-te/rsbs/rsb" {
    description
      "RSVP-TE generic data augmentation pertaining to session";
    leaf fspec-average-rate {
      type rt-types:bandwidth-ieee-float32;
      units "Bytes per second";
      description
        "Fspec Token Bucket Average Rate";
      reference
        "RFC2210";
    }
    leaf fspec-size {
      type rt-types:bandwidth-ieee-float32;
      units "Bytes per second";
      description
        "Fspec Token Bucket Burst Rate";
      reference
        "RFC2210";
    }
    leaf fspec-peak-rate {
      type rt-types:bandwidth-ieee-float32;
      units "Bytes per second";
      description
        "Fspec Token Bucket Peak Data Rate";
      reference
        "RFC2210";
    }
    leaf min-policed-unit {
      type uint32;
      description
        "Fspec Minimum Policed Unit";
      reference
        "RFC2210";
    }
    leaf max-packet-size {
      type uint32;
      description
        "Fspec Maximum Packet Size";
      reference
        "RFC2210";
    }
  }

  augment "/rt:routing/rt:control-plane-protocols/"
        + "rt:control-plane-protocol/rsvp:rsvp/rsvp:neighbors" {
    description
      "RSVP-TE generic data augmentation pertaining to neighbors";
    /* To be added */
  }

  /**
   * RSVP-TE generic augmentations of generic TE model.
   */
  /* TE tunnel augmentation */

  augment "/te:te/te:tunnels/te:tunnel" {
    when "/te:te/te:tunnels/te:tunnel"
       + "/te:primary-paths/te:primary-path"
       + "/te:signaling-type = 'te-types:path-setup-rsvp'" {
      description
        "When the path signaling protocol is RSVP-TE ";
    }
    description
      "RSVP-TE generic data augmentation pertaining to TE tunnels";
    uses lsp-properties;
    uses tunnel-properties;
  }

  /* TE LSP augmentation */

  grouping rsvp-te-lsp-error-info {
    description
      "Grouping for RSVP-TE error reporting information";
    leaf rsvp-message-type {
      type identityref {
        base rsvp-message-type;
      }
      description
        "The RSVP message type that delivered the error";
    }
    leaf rsvp-error-code {
      type uint8;
      description
        "RSVP error code";
      reference
        "RFC2205";
    }
    leaf rsvp-error-subcode {
      type uint16;
      description
        "RSVP Error sub-codes";
      reference
        "RFC2205";
    }
  }

  grouping rsvp-te-lsp-properties {
    description
      "RSVP-TE LSP properties grouping";
    leaf associated-rsvp-session {
      type leafref {
        path "/rt:routing/rt:control-plane-protocols/"
           + "rt:control-plane-protocol/rsvp:rsvp/rsvp:globals/"
           + "rsvp:sessions/session-te/tunnel-id";
      }
      config false;
      description
        "If the signalling protocol specified for this path is
         RSVP-TE, this leaf provides a reference to the associated
         session within the RSVP-TE protocol sessions list, such
         that details of the signaling can be retrieved.";
    }
    uses lsp-properties;
    uses lsp-explicit-route-information-state;
    uses lsp-record-route-information-state;
  }

  augment "/te:te/te:lsps/te:lsp" {
    when "/te:te/te:lsps/te:lsp"
       + "/te:signaling-type = 'te-types:path-setup-rsvp'" {
      description
        "When the signaling protocol is RSVP-TE ";
    }
    description
      "RSVP-TE generic data augmentation pertaining to specific TE
       LSP";
    uses rsvp-te-lsp-properties;
  }

  augment "/te:te/te:tunnels/te:tunnel/te:primary-paths"
        + "/te:primary-path/te:lsps/te:lsp" {
    when "/te:te/te:tunnels/te:tunnel/te:primary-paths"
       + "/te:primary-path/te:lsps/te:lsp"
       + "/te:signaling-type = 'te-types:path-setup-rsvp'" {
      description
        "When the signaling protocol is RSVP-TE ";
    }
    description
      "RSVP-TE generic data augmentation pertaining to specific TE
       LSP";
    uses rsvp-te-lsp-properties;
  }

  augment "/te:te/te:tunnels/te:tunnel/te:primary-paths"
        + "/te:primary-path"
        + "/te:lsp-provisioning-error-infos"
        + "/te:lsp-provisioning-error-info" {
    description
      "Augmentation for RSVP-TE per LSP error reason";
    uses rsvp-te-lsp-error-info;
  }

  augment "/te:te/te:tunnels/te:tunnel/te:primary-paths"
        + "/te:primary-path/te:lsps/te:lsp"
        + "/te:lsp-provisioning-error-infos"
        + "/te:lsp-provisioning-error-info" {
    when "/te:te/te:tunnels/te:tunnel/te:primary-paths"
       + "/te:primary-path/te:lsps/te:lsp"
       + "/te:signaling-type = 'te-types:path-setup-rsvp'" {
      description
        "When the signaling protocol is RSVP-TE ";
    }
    description
      "Augmentation for RSVP-TE per path error reason";
    uses rsvp-te-lsp-error-info;
  }

  augment "/te:te/te:tunnels/te:tunnel/te:secondary-paths"
        + "/te:secondary-path/te:lsps/te:lsp" {
    when "/te:te/te:tunnels/te:tunnel/te:secondary-paths"
       + "/te:secondary-path/te:lsps/te:lsp"
       + "/te:signaling-type = 'te-types:path-setup-rsvp'" {
      description
        "When the signaling protocol is RSVP-TE ";
    }
    description
      "RSVP-TE generic data augmentation pertaining to specific TE
       LSP";
    uses rsvp-te-lsp-properties;
  }

  augment "/te:te/te:tunnels/te:tunnel/te:secondary-paths"
        + "/te:secondary-path"
        + "/te:lsp-provisioning-error-infos"
        + "/te:lsp-provisioning-error-info" {
    description
      "Augmentation for RSVP-TE per path error reason";
    uses rsvp-te-lsp-error-info;
  }

  augment "/te:te/te:tunnels/te:tunnel/te:secondary-paths"
        + "/te:secondary-path/te:lsps/te:lsp"
        + "/te:lsp-provisioning-error-infos"
        + "/te:lsp-provisioning-error-info" {
    when "/te:te/te:tunnels/te:tunnel/te:secondary-paths"
       + "/te:secondary-path/te:lsps/te:lsp"
       + "/te:signaling-type = 'te-types:path-setup-rsvp'" {
      description
        "When the signaling protocol is RSVP-TE ";
    }
    description
      "Augmentation for RSVP-TE per LSP error reason";
    uses rsvp-te-lsp-error-info;
  }

  /* TE interface augmentation */

  augment "/te:te/te-dev:interfaces/te-dev:interface" {
    description
      "RSVP-TE generic data augmentation pertaining to specific TE
       interface";
  }
}
