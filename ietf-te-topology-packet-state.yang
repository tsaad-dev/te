module ietf-te-topology-packet-state {
  yang-version 1.1;
  namespace
    "urn:ietf:params:xml:ns:yang:ietf-te-topology-packet-state";

  prefix "tet-pkt-s";

  import ietf-te-topology-packet {
    prefix "tet-pkt";
  }

  import ietf-network-state {
    prefix "nw-s";
    reference
      "RFC 8345: A YANG Data Model for Network Topologies";
  }

  import ietf-network-topology-state {
    prefix "nt-s";
    reference
      "RFC 8345: A YANG Data Model for Network Topologies";
  }

  import ietf-te-topology-state {
    prefix "tet-s";
    reference
      "I-D.ietf-teas-yang-te-topo: YANG Data Model for Traffic
       Engineering (TE) Topologies";
  }

  import ietf-te-types {
    prefix "te-types";
    reference
      "I-D.ietf-teas-yang-te-types: Traffic Engineering Common YANG
       Types";
  }

  import ietf-te-packet-types {
    prefix "te-packet-types";
    reference
      "I-D.ietf-teas-yang-te-types: Traffic Engineering Common YANG
       Types";
  }

  organization
    "Traffic Engineering Architecture and Signaling (TEAS)
     Working Group";

  contact
    "WG Web:   <http://tools.ietf.org/wg/teas/>
     WG List:  <mailto:teas@ietf.org>

     Editor:   Xufeng Liu
               <mailto:xufeng.liu.ietf@gmail.com>

     Editor:   Igor Bryskin
               <mailto:Igor.Bryskin@huawei.com>

     Editor:   Vishnu Pavan Beeram
               <mailto:vbeeram@juniper.net>

     Editor:   Tarek Saad
               <mailto:tsaad@cisco.com>

     Editor:   Himanshu Shah
               <mailto:hshah@ciena.com>

     Editor:   Oscar Gonzalez De Dios
               <mailto:oscar.gonzalezdedios@telefonica.com>";

  description
    "YANG data model for representing operational state information
     of PSC (Packet Switching) TE Topologies, when NMDA is not
      supported.

     Copyright (c) 2018 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX; see the
     RFC itself for full legal notices.";

  revision 2020-07-03 {
    description
      "Initial revision";
    reference
      "RFC XXXX: YANG Data Model for Layer 3 TE Topologies";
  }

  /*
   * Augmentations
   */
  /* Augmentations to network-types */
  augment "/nw-s:networks/nw-s:network/nw-s:network-types/"
    + "tet-s:te-topology" {
    description
      "Defines the packet TE topology type.";
    container packet {
      presence "Indicates packet TE topology.";
      description
        "Its presence identifies the packet TE topology type.";
    }
  }

  /* Augmentations to connectivity-matrix */
  augment "/nw-s:networks/nw-s:network/nw-s:node/tet-s:te/"
    + "tet-s:te-node-attributes/tet-s:connectivity-matrices" {
    when "../../../../nw-s:network-types/tet-s:te-topology/"
      + "tet-pkt-s:packet" {
      description
        "Augment only for packet TE topology";
    }
    description
      "Parameters for PSC (Packet Switching) TE topology.";
    uses te-packet-types:performance-metrics-attributes-packet {
      if-feature tet-pkt:te-performance-metric;
    }
    uses
      te-packet-types:performance-metrics-throttle-container-packet {
      if-feature tet-pkt:te-performance-metric;
    }
  }

  augment "/nw-s:networks/nw-s:network/nw-s:node/tet-s:te/"
        + "tet-s:te-node-attributes/tet-s:connectivity-matrices/"
        + "tet-s:connectivity-matrix" {
    when "../../../../../nw-s:network-types/tet-s:te-topology/"
      + "tet-pkt-s:packet" {
      description
        "Augment only for packet TE topology";
    }
    description
      "Parameters for PSC TE topology.";
    uses te-packet-types:performance-metrics-attributes-packet {
      if-feature tet-pkt:te-performance-metric;
    }
    uses
      te-packet-types:performance-metrics-throttle-container-packet {
      if-feature tet-pkt:te-performance-metric;
    }
  }

  augment "/nw-s:networks/nw-s:network/nw-s:node/tet-s:te/"
        + "tet-s:information-source-entry/"
        + "tet-s:connectivity-matrices" {
    when "../../../../nw-s:network-types/tet-s:te-topology/"
      + "tet-pkt-s:packet" {
      description
        "Augment only for packet TE topology";
    }
    description
      "Parameters for PSC TE topology.";
    uses te-packet-types:performance-metrics-attributes-packet {
      if-feature tet-pkt:te-performance-metric;
    }
    uses
      te-packet-types:performance-metrics-throttle-container-packet {
      if-feature tet-pkt:te-performance-metric;
    }
  }

  augment "/nw-s:networks/nw-s:network/nw-s:node/tet-s:te/"
        + "tet-s:information-source-entry/"
        + "tet-s:connectivity-matrices/"
        + "tet-s:connectivity-matrix" {
    when "../../../../../nw-s:network-types/tet-s:te-topology/"
      + "tet-pkt-s:packet" {
      description
        "Augment only for packet TE topology";
    }
    description
      "Parameters for PSC TE topology.";
    uses te-packet-types:performance-metrics-attributes-packet {
      if-feature tet-pkt:te-performance-metric;
    }
    uses
      te-packet-types:performance-metrics-throttle-container-packet {
      if-feature tet-pkt:te-performance-metric;
    }
  }

  /* Augmentations to tunnel-termination-point */
  augment "/nw-s:networks/nw-s:network/nw-s:node/tet-s:te/"
        + "tet-s:tunnel-termination-point/"
        + "tet-s:local-link-connectivities" {
    when "../../../../nw-s:network-types/tet-s:te-topology/"
      + "tet-pkt-s:packet" {
      description
        "Augment only for packet TE topology";
    }
    description
      "Parameters for PSC TE topology.";
    uses te-packet-types:performance-metrics-attributes-packet {
      if-feature tet-pkt:te-performance-metric;
    }
    uses
      te-packet-types:performance-metrics-throttle-container-packet {
      if-feature tet-pkt:te-performance-metric;
    }
  }

  augment "/nw-s:networks/nw-s:network/nw-s:node/tet-s:te/"
        + "tet-s:tunnel-termination-point/"
        + "tet-s:local-link-connectivities/"
        + "tet-s:local-link-connectivity" {
    when "../../../../../nw-s:network-types/tet-s:te-topology/"
      + "tet-pkt-s:packet" {
      description
        "Augment only for packet TE topology";
    }
    description
      "Parameters for PSC TE topology.";
    uses te-packet-types:performance-metrics-attributes-packet {
      if-feature tet-pkt:te-performance-metric;
    }
    uses
      te-packet-types:performance-metrics-throttle-container-packet {
      if-feature tet-pkt:te-performance-metric;
    }
  }

  /* Augmentations to te-link-attributes */
  augment "/nw-s:networks/tet-s:te/tet-s:templates/"
        + "tet-s:link-template/tet-s:te-link-attributes" {
    when "tet-s:interface-switching-capability "
      + "[tet-s:switching-capability = 'te-types:switching-psc1']" {
      description
        "Valid only for PSC";
    }
    description
      "Parameters for PSC TE topology.";
    uses te-packet-types:performance-metrics-attributes-packet {
      if-feature tet-pkt:te-performance-metric;
    }
    uses
      te-packet-types:performance-metrics-throttle-container-packet {
      if-feature tet-pkt:te-performance-metric;
    }
  }

  augment "/nw-s:networks/nw-s:network/nt-s:link/tet-s:te/"
        + "tet-s:te-link-attributes" {
    when "(../../../nw-s:network-types/tet-s:te-topology/"
      + "tet-pkt-s:packet) and "
      + "(tet-s:interface-switching-capability "
      + "[tet-s:switching-capability = 'te-types:switching-psc1'])" {
      description "Valid only for PSC";
    }
    description
      "Parameters for PSC TE topology.";
    uses te-packet-types:performance-metrics-attributes-packet {
      if-feature tet-pkt:te-performance-metric;
    }
    uses
      te-packet-types:performance-metrics-throttle-container-packet {
      if-feature tet-pkt:te-performance-metric;
    }
  }

  augment "/nw-s:networks/nw-s:network/nt-s:link/tet-s:te/"
        + "tet-s:information-source-entry" {
    when "(../../../nw-s:network-types/tet-s:te-topology/"
      + "tet-pkt-s:packet) and "
      + "(tet-s:interface-switching-capability "
      + "[tet-s:switching-capability = 'te-types:switching-psc1'])" {
      description "Valid only for PSC";
    }
    description
      "Parameters for PSC TE topology.";
    uses te-packet-types:performance-metrics-attributes-packet {
      if-feature tet-pkt:te-performance-metric;
    }
    uses
      te-packet-types:performance-metrics-throttle-container-packet {
      if-feature tet-pkt:te-performance-metric;
    }
  }

  /* Augmentations to interface-switching-capability */
  augment "/nw-s:networks/tet-s:te/tet-s:templates/"
        + "tet-s:link-template/tet-s:te-link-attributes/"
        + "tet-s:interface-switching-capability" {
    when "tet-s:switching-capability = 'te-types:switching-psc1' " {
      description "Valid only for PSC";
    }
    description
      "Parameters for PSC TE topology.";
    uses tet-pkt:packet-switch-capable-container;
  }

  augment "/nw-s:networks/nw-s:network/nt-s:link/tet-s:te/"
        + "tet-s:te-link-attributes/"
        + "tet-s:interface-switching-capability" {
    when "(../../../../nw-s:network-types/tet-s:te-topology/"
      + "tet-pkt-s:packet) and "
      + "(tet-s:switching-capability = 'te-types:switching-psc1')" {
      description "Valid only for PSC";
    }
    description
      "Parameters for PSC TE topology.";
    uses tet-pkt:packet-switch-capable-container;
  }

  augment "/nw-s:networks/nw-s:network/nt-s:link/tet-s:te/"
        + "tet-s:information-source-entry/"
        + "tet-s:interface-switching-capability" {
    when "(../../../../nw-s:network-types/tet-s:te-topology/"
      + "tet-pkt-s:packet) and "
      + "(tet-s:switching-capability = 'te-types:switching-psc1')" {
      description
        "Valid only for PSC";
    }
    description
      "Parameters for PSC TE topology.";
    uses tet-pkt:packet-switch-capable-container;
  }
}
